SEC-MIB DEFINITIONS ::= BEGIN

IMPORTS
    MODULE-IDENTITY, OBJECT-TYPE, UInteger32,
    netSnmp                                 FROM NET-SNMP-MIB
;

sec MODULE-IDENTITY
    LAST-UPDATED "202206270000Z"
    ORGANIZATION "www.uminho.pt"
    CONTACT-INFO    
	 "postal:   Luís Carneiro
          email:    pg46541@alunos.uminho.pt"
    DESCRIPTION
	"MIB que permite a comunicação de um manager com vários agentes por SNMPv2c,
   com mecanismos de segurança que simulam as garantias de SNMPv3"
    REVISION     "202206270000Z"
    DESCRIPTION
	"Definição final do documento"
    ::= { netSnmp 567 }

logTable OBJECT-TYPE
    SYNTAX      SEQUENCE OF logTableEntries
    MAX-ACCESS  not-accessible
    STATUS      current
    DESCRIPTION "..."
    ::= { sec 2 }

logTableVirtualEntry OBJECT-TYPE
    SYNTAX      logTableEntries
    MAX-ACCESS  not-accessible
    STATUS      current
    DESCRIPTION "..."
    INDEX { idOper } ::= { logTable 1 }

TypeOfTheEntries ::=
   SEQUENCE {
      idOper            Unsigned32(10000..99999)
      typeOper          Unsigned32(0..1)
      idSource          OCTET STRING
      idDest            OCTET STRING
      oidArg            OCTET STRING
      valueArg          OCTET STRING
      sizeArg           Unsigned32
      statusOper        Unsigned32(0..3)
      requestTimestamp  DateAndTime
      ttlOper           Unsigned32
}

idOper OBJECT-TYPE
   SYNTAX       Unsigned32(10000..99999)
   MAX-ACCESS   read-write
   STATUS       current
DESCRIPTION     "identificador inteiro da operação recebida
pelo agente proxy (número aleatório e unívoco, gerado pelo gestor e
verificado pelo proxy); este objeto serve de chave da tabela; tem 5
dígitos, portanto o seu limite inferior é 100000 e o superior é 99999"
::= { logTableVirtualEntry 1 }

typeOper OBJECT-TYPE
   SYNTAX       Unsigned32(0..1)
   MAX-ACCESS   read-write
   STATUS       current
DESCRIPTION     "tipo de operação SNMP (get, getnext);a identificação
é feita através dum número inteiro (0 para o get e 1 para o getnext)"
::= { logTableVirtualEntry 2 }

idSource OBJECT-TYPE
   SYNTAX       OCTET STRING
   MAX-ACCESS   read-write
   STATUS       current
DESCRIPTION     "identificador string da fonte do pedido (um alias/nome
que identifica um gestor)"
::= { logTableVirtualEntry 3 }

idDest OBJECT-TYPE
   SYNTAX       OCTET STRING
   MAX-ACCESS   read-write
   STATUS       current
DESCRIPTION     "identificador string do destino onde a operação será
executada (um alias/nome que identifica um gestor SNMPv2c)"
::= { logTableVirtualEntry 4 }

oidArg OBJECT-TYPE
   SYNTAX       OCTET STRING
   MAX-ACCESS   read-write
   STATUS       current
DESCRIPTION     "OID em string do objeto da MIB que é argumento da
operação a ser executada no agente SNMPv2c remoto"
::= { logTableVirtualEntry 5 }

valueArg OBJECT-TYPE
   SYNTAX       OCTET STRING
   MAX-ACCESS   read-only
   STATUS       current
DESCRIPTION     "valor em string do objeto referido por oidArg que
é o resultado recebido no agente proxy vindo do agente SNMPv2c remoto"
::= { logTableVirtualEntry 6 }

sizeArg OBJECT-TYPE
   SYNTAX       Unsigned32
   MAX-ACCESS   read-only
   STATUS       current
DESCRIPTION     "tamanho em bytes do valueArg; enquanto o valor de
valueArg não é devolvido pelo agente SNMPv2c remoto, sizeArg deve
ser igual a zero; quando o agente proxy recebe a resposta do agente
SNMPv2c remoto grava o valor da instância do objeto em valueArg e
coloca sizeArg com o tamanho desse valor (em bytes)"
::= { logTableVirtualEntry 7 }

statusOper OBJECT-TYPE
   SYNTAX       Unsigned32(0..3)
   MAX-ACCESS   read-only
   STATUS       current
DESCRIPTION     "do tipo inteiro, assume o valor 0 quando o objeto
não está completamente definido na tabela (falta o OID), 1 quando
está (e está à espera da resposta), 2 quando ocorreu um erro ao
fazer query, e 3 quando o objeto está válido"
::= { logTableVirtualEntry 8 }

requestTimestamp OBJECT-TYPE
   SYNTAX       DateAndTime
   MAX-ACCESS   read-only
   STATUS       current
DESCRIPTION     "marca o timestamp que o manager colocou o pedido na tabela"
::= { logTableVirtualEntry 9 }

ttlOper OBJECT-TYPE
   SYNTAX       Unsigned32
   MAX-ACCESS   read-only
   STATUS       current
DESCRIPTION     "identifica por quanto tempo em segundos o pedido do
agente é válido"
::= { logTableVirtualEntry 10 }


END
